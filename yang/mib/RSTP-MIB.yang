/*
 * This YANG module has been generated by smidump 0.5.0:
 *
 *      smidump -f yang RSTP-MIB
 *
 * Do not edit. Edit the source file instead!
 */

module RSTP-MIB {

  namespace "urn:ietf:params:xml:ns:yang:smiv2:RSTP-MIB";
  prefix "rstp-mib";

  import BRIDGE-MIB {
    prefix "bridge-mib";
  }

  import ietf-yang-smiv2 {
    prefix "smiv2";
  }

  organization
   "IETF Bridge MIB Working Group";

  contact
   "Email: Bridge-mib@ietf.org";

  description
   "The Bridge MIB Extension module for managing devices
    that support the Rapid Spanning Tree Protocol defined
    by IEEE 802.1w.
    
    Copyright (C) The Internet Society (2005).  This version of
    this MIB module is part of RFC 4318; See the RFC itself for
    full legal notices.";

  revision 2005-12-07 {
    description
     "The initial version of this MIB module as published in
      RFC 4318.";
  }


  container RSTP-MIB {
    config false;

    container dot1dStp {
      smiv2:oid "1.3.6.1.2.1.17.2";

      leaf dot1dStpVersion {
        type enumeration {
          enum "stpCompatible" {
            value "0";
          }
          enum "rstp" {
            value "2";
          }
        }
        description
         "The version of Spanning Tree Protocol the bridge is
          currently running.  The value 'stpCompatible(0)'
          indicates the Spanning Tree Protocol specified in
          IEEE 802.1D-1998 and 'rstp(2)' indicates the Rapid
          Spanning Tree Protocol specified in IEEE 802.1w and
          clause 17 of 802.1D-2004.  The values are directly from
          the IEEE standard.  New values may be defined as future
          versions of the protocol become available.
          
          The value of this object MUST be retained across
          reinitializations of the management system.";
        reference
         "IEEE 802.1w clause 14.8.1, 17.12, 17.16.1";
        smiv2:defval "rstp";
        smiv2:max-access "read-write";
        smiv2:oid "1.3.6.1.2.1.17.2.16";
      }

      leaf dot1dStpTxHoldCount {
        type int32 {
          range "1..10";
        }
        description
         "The value used by the Port Transmit state machine to limit
          the maximum transmission rate.
          
          The value of this object MUST be retained across
          reinitializations of the management system.";
        reference
         "IEEE 802.1w clause 17.16.6";
        smiv2:defval "3";
        smiv2:max-access "read-write";
        smiv2:oid "1.3.6.1.2.1.17.2.17";
      }
    }
  }

  smiv2:alias "dot1dStpExtPortTable" {
    description
     "A table that contains port-specific Rapid Spanning Tree
      information.";
    smiv2:oid "1.3.6.1.2.1.17.2.19";
  }

  smiv2:alias "dot1dStpExtPortEntry" {
    description
     "A list of Rapid Spanning Tree information maintained by
      each port.";
    smiv2:oid "1.3.6.1.2.1.17.2.19.1";
  }

  augment "/bridge-mib:BRIDGE-MIB/bridge-mib:dot1dStpPortTable/bridge-mib:dot1dStpPortEntry" {
    description
     "A list of Rapid Spanning Tree information maintained by
      each port.";
    smiv2:oid "1.3.6.1.2.1.17.2.19.1";

    leaf dot1dStpPortProtocolMigration {
      type boolean;
      description
       "When operating in RSTP (version 2) mode, writing true(1)
        to this object forces this port to transmit RSTP BPDUs.
        Any other operation on this object has no effect and
        it always returns false(2) when read.";
      reference
       "IEEE 802.1w clause 14.8.2.4, 17.18.10, 17.26";
      smiv2:max-access "read-write";
      smiv2:oid "1.3.6.1.2.1.17.2.19.1.1";
    }

    leaf dot1dStpPortAdminEdgePort {
      type boolean;
      description
       "The administrative value of the Edge Port parameter.  A
        value of true(1) indicates that this port should be
        assumed as an edge-port, and a value of false(2) indicates
        that this port should be assumed as a non-edge-port.
        
        
        
        Setting this object will also cause the corresponding
        instance of dot1dStpPortOperEdgePort to change to the
        same value.  Note that even when this object's value
        is true, the value of the corresponding instance of
        dot1dStpPortOperEdgePort can be false if a BPDU has
        been received.
        
        The value of this object MUST be retained across
        reinitializations of the management system.";
      reference
       "IEEE 802.1t clause 14.8.2, 18.3.3";
      smiv2:max-access "read-write";
      smiv2:oid "1.3.6.1.2.1.17.2.19.1.2";
    }

    leaf dot1dStpPortOperEdgePort {
      type boolean;
      description
       "The operational value of the Edge Port parameter.  The
        object is initialized to the value of the corresponding
        instance of dot1dStpPortAdminEdgePort.  When the
        corresponding instance of dot1dStpPortAdminEdgePort is
        set, this object will be changed as well.  This object
        will also be changed to false on reception of a BPDU.";
      reference
       "IEEE 802.1t clause 14.8.2, 18.3.4";
      smiv2:max-access "read-only";
      smiv2:oid "1.3.6.1.2.1.17.2.19.1.3";
    }

    leaf dot1dStpPortAdminPointToPoint {
      type enumeration {
        enum "forceTrue" {
          value "0";
        }
        enum "forceFalse" {
          value "1";
        }
        enum "auto" {
          value "2";
        }
      }
      description
       "The administrative point-to-point status of the LAN segment
        attached to this port, using the enumeration values of the
        IEEE 802.1w clause.  A value of forceTrue(0) indicates
        that this port should always be treated as if it is
        connected to a point-to-point link.  A value of
        forceFalse(1) indicates that this port should be treated as
        having a shared media connection.  A value of auto(2)
        indicates that this port is considered to have a
        point-to-point link if it is an Aggregator and all of its
        
        
        
        members are aggregatable, or if the MAC entity
        is configured for full duplex operation, either through
        auto-negotiation or by management means.  Manipulating this
        object changes the underlying adminPortToPortMAC.
        
        The value of this object MUST be retained across
        reinitializations of the management system.";
      reference
       "IEEE 802.1w clause 6.4.3, 6.5, 14.8.2";
      smiv2:max-access "read-write";
      smiv2:oid "1.3.6.1.2.1.17.2.19.1.4";
    }

    leaf dot1dStpPortOperPointToPoint {
      type boolean;
      description
       "The operational point-to-point status of the LAN segment
        attached to this port.  It indicates whether a port is
        considered to have a point-to-point connection.
        If adminPointToPointMAC is set to auto(2), then the value
        of operPointToPointMAC is determined in accordance with the
        specific procedures defined for the MAC entity concerned,
        as defined in IEEE 802.1w, clause 6.5.  The value is
        determined dynamically; that is, it is re-evaluated whenever
        the value of adminPointToPointMAC changes, and whenever
        the specific procedures defined for the MAC entity evaluate
        a change in its point-to-point status.";
      reference
       "IEEE 802.1w clause 6.4.3, 6.5, 14.8.2";
      smiv2:max-access "read-only";
      smiv2:oid "1.3.6.1.2.1.17.2.19.1.5";
    }

    leaf dot1dStpPortAdminPathCost {
      type int32 {
        range "0..200000000";
      }
      description
       "The administratively assigned value for the contribution
        of this port to the path cost of paths toward the spanning
        tree root.
        
        Writing a value of '0' assigns the automatically calculated
        default Path Cost value to the port.  If the default Path
        Cost is being used, this object returns '0' when read.
        
        This complements the object dot1dStpPortPathCost or
        dot1dStpPortPathCost32, which returns the operational value
        of the path cost.
        
        
        
        The value of this object MUST be retained across
        reinitializations of the management system.";
      reference
       "IEEE 802.1D-1998: Section 8.5.5.3";
      smiv2:max-access "read-write";
      smiv2:oid "1.3.6.1.2.1.17.2.19.1.6";
    }
  }

  smiv2:alias "rstpMIB" {
    smiv2:oid "1.3.6.1.2.1.134";
  }

  smiv2:alias "rstpNotifications" {
    smiv2:oid "1.3.6.1.2.1.134.0";
  }

  smiv2:alias "rstpObjects" {
    smiv2:oid "1.3.6.1.2.1.134.1";
  }

  smiv2:alias "rstpConformance" {
    smiv2:oid "1.3.6.1.2.1.134.2";
  }

  smiv2:alias "rstpGroups" {
    smiv2:oid "1.3.6.1.2.1.134.2.1";
  }

  smiv2:alias "rstpCompliances" {
    smiv2:oid "1.3.6.1.2.1.134.2.2";
  }

}
