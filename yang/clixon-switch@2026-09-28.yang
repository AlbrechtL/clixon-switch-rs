module clixon-switch {
  yang-version 1.1;
  namespace "urn:github:albrechtl:clixon-switch";
  prefix sw;

  // The modules imported here make up the switch's data model.
  // scripts/vendor-yang.sh copies their import closure from openconfig/public.
  import openconfig-interfaces { prefix oc-if; }
  import openconfig-if-ethernet { prefix oc-eth; }
  import openconfig-vlan { prefix oc-vlan; }
  import openconfig-vlan-types { prefix oc-vlan-types; }
  import openconfig-if-ip { prefix oc-ip; }
  import openconfig-inet-types { prefix oc-inet; }
  import openconfig-yang-types { prefix oc-yang; }
  import openconfig-spanning-tree { prefix oc-stp; }
  import openconfig-spanning-tree-types { prefix oc-stp-types; }
  // SNMP: ietf-snmp configures the agent (snmpd). clixon_snmp serves the
  // MIBs below (translated by scripts/mib-to-yang.sh, all config false)
  // from state data; importing them makes clixon load them.
  import ietf-snmp { prefix snmp; }
  import BRIDGE-MIB { prefix bridge-mib; }
  import Q-BRIDGE-MIB { prefix q-bridge; }
  import RSTP-MIB { prefix rstp-mib; }

  organization "clixon-switch-rs";
  contact "https://github.com/AlbrechtL/clixon-switch-rs";
  description
    "Top-level module of the clixon-switch backend: switch ports in one
     VLAN-aware bridge, and routed VLAN interfaces with static IPv4
     addresses or a DHCP client, and spanning tree (STP, RSTP, MSTP), as
     modelled by OpenConfig.

     The switch runs in one of two VLAN modes (switch/config/vlan-mode):
     DOT1Q, with the VLANs declared in vlans and access or trunk ports; or
     PORT_BASED, with ports in disjoint port-based-vlans groups and no tags.

     SNMP: an SNMPv3 agent, read-only, configured in /snmp of ietf-snmp
     (engine, USM users, VACM). It serves SNMPv2-MIB's system group and
     IF-MIB, and BRIDGE-MIB, Q-BRIDGE-MIB and RSTP-MIB from the state of
     the switch. /system/config holds sysContact and sysLocation.

     The backend implements only part of these modules. It rejects any other
     configuration when validating a commit (see switch-model's supported.rs).
     There are no deviation statements: clixon 7.8 does not reject data for
     nodes marked 'deviate not-supported', it only skips their must
     checks.";

  revision 2026-09-28 {
    description
      "The first-login setup creates the admin account: set-password takes
       its username.";
  }
  revision 2026-09-27 {
    description
      "System state: the revision the firmware was built from, os-build-id.
       The admin password: setup-required, and the RPCs set-password and
       factory-reset.";
  }
  revision 2026-09-17 {
    description
      "SNMPv3 agent, read-only: /snmp of ietf-snmp, the engine ID in use,
       and BRIDGE-MIB, Q-BRIDGE-MIB and RSTP-MIB as state data.
       System contact and location.";
  }
  revision 2026-09-16 {
    description
      "VLAN database, trunk ports, VLAN mode and port-based VLAN groups.
       State of the DHCP client's lease.
       Spanning tree: identity STP, and the CIST's bridge priority and
       ports in MSTP.
       System state: host name, OS release, uptime, load and memory.";
  }
  revision 2026-09-15 {
    description "Initial revision.";
  }

  // The VLAN database. openconfig-vlan only defines the grouping; its user,
  // openconfig-network-instance, is too big for the switch.
  uses oc-vlan:vlan-top;

  grouping switch-config {
    leaf vlan-mode {
      type enumeration {
        enum DOT1Q {
          description
            "IEEE 802.1Q: VLANs declared in /vlans, ports in access or
             trunk mode.";
        }
        enum PORT_BASED {
          description
            "Ports in disjoint groups (/port-based-vlans), untagged. Ports
             forward only to ports of their own group.";
        }
      }
      default DOT1Q;
      description "How ports are assigned to VLANs.";
    }
  }

  container switch {
    description "Switch-wide settings.";
    container config {
      uses switch-config;
    }
    container state {
      config false;
      uses switch-config;
    }
  }

  grouping system-config {
    leaf contact {
      type string {
        length "0..255";
      }
      description
        "Who is responsible for the switch, and how to reach them: SNMP's
         sysContact. One line.";
    }
    leaf location {
      type string {
        length "0..255";
      }
      description "Where the switch is: SNMP's sysLocation. One line.";
    }
  }

  // ietf-system and openconfig-system are too big for what the switch
  // reports, and mostly configuration it does not implement.
  container system {
    description "The switch as a whole.";
    container config {
      uses system-config;
    }
    container state {
      config false;
      description
        "The configuration in effect, and what is read from /proc and
         os-release on every request.";
      uses system-config;
      leaf hostname {
        type string;
        description "Kernel host name.";
      }
      leaf os-name {
        type string;
        description "NAME of os-release.";
      }
      leaf os-version {
        type string;
        description "VERSION of os-release: the firmware version.";
      }
      leaf os-build-id {
        type string;
        description
          "BUILD_ID of os-release: the revision of meta-ethernet-switch-os
           the firmware was built from. The firmware version starts out as
           that revision too; once releases are tagged it is the tag, and
           this is the only leaf naming the commit.";
      }
      leaf kernel-release {
        type string;
        description "Linux kernel release.";
      }
      leaf current-datetime {
        type oc-yang:date-and-time;
        description
          "System clock, in UTC. The switch has no real-time clock: it
           starts at the Unix epoch on every boot.";
      }
      leaf uptime {
        type uint64;
        units seconds;
        description "Time since boot.";
      }
      leaf load-average-1 {
        type decimal64 {
          fraction-digits 2;
        }
        description "Load average over 1 minute.";
      }
      leaf load-average-5 {
        type decimal64 {
          fraction-digits 2;
        }
        description "Load average over 5 minutes.";
      }
      leaf load-average-15 {
        type decimal64 {
          fraction-digits 2;
        }
        description "Load average over 15 minutes.";
      }
      leaf memory-total {
        type uint64;
        units kilobytes;
        description "Usable RAM (MemTotal).";
      }
      leaf memory-available {
        type uint64;
        units kilobytes;
        description
          "RAM available to new processes without swapping
           (MemAvailable).";
      }
      leaf setup-required {
        type boolean;
        description
          "True until the admin account is set up, after the first boot or a
           factory reset. Until then there is no account to log in with, and
           set-password creates it: it takes a username and needs no
           current-password.";
      }
    }
  }

  rpc set-password {
    description
      "Sets the admin password, for SSH, the serial console and the web
       interface.

       While setup-required is true, this is the first-login setup: it
       creates the admin account with username and new-password.
       Afterwards it changes the password of that account and fails with
       access-denied if current-password is missing or wrong.";
    input {
      leaf username {
        type string {
          pattern '[a-z_][a-z0-9_-]{0,31}';
        }
        description
          "The name of the admin account. Required during the setup, not
           allowed afterwards: the name stays until a factory reset. It
           must not be the name of an existing user or group, such as
           root.";
      }
      leaf current-password {
        type string;
        description "The password now. Not needed during the setup.";
      }
      leaf new-password {
        type string {
          length "8..128";
        }
        mandatory true;
        description "The new password. No control characters.";
      }
    }
  }

  rpc factory-reset {
    description
      "Erases the whole data partition on the next boot and reboots now:
       the saved configuration, the admin account (setup-required is true
       again), the SSH host keys and the HTTPS certificate. The firmware
       stays.";
  }

  grouping port-based-vlan-group-config {
    leaf id {
      type oc-vlan-types:vlan-id;
      description
        "Group id. Also the VLAN id the group uses inside the switch, so a
         routed-vlan interface refers to the group by it.";
    }
    leaf name {
      type string;
      description "Group name; routed-vlan interfaces may refer to it.";
    }
    leaf-list port {
      type leafref {
        path "/oc-if:interfaces/oc-if:interface/oc-if:name";
      }
      description
        "Member ports. A port is a member of at most one group.";
    }
  }

  container port-based-vlans {
    description
      "Port-based VLAN groups, used in vlan-mode PORT_BASED only.";
    list group {
      key "id";
      leaf id {
        type leafref {
          path "../config/id";
        }
      }
      container config {
        uses port-based-vlan-group-config;
      }
      container state {
        config false;
        uses port-based-vlan-group-config;
      }
    }
  }

  // OpenConfig models only whether a DHCP client runs
  // (ipv4/config/dhcp-client) and the origin of an address, not the lease.
  augment "/oc-if:interfaces/oc-if:interface/oc-vlan:routed-vlan/"
        + "oc-ip:ipv4/oc-ip:state" {
    description
      "DHCP client lease of a routed VLAN interface.";
    container dhcp-lease {
      description
        "The lease the DHCP client currently holds. Absent while
         ipv4/config/dhcp-client is false or no lease is bound.";
      leaf address {
        type oc-inet:ipv4-address;
        description "Leased address.";
      }
      leaf prefix-length {
        type uint8 {
          range "0..32";
        }
        description "Prefix length of the leased address.";
      }
      leaf-list router {
        type oc-inet:ipv4-address;
        ordered-by user;
        description
          "Routers offered by the server. The first one is the default
           gateway.";
      }
      leaf-list dns-server {
        type oc-inet:ipv4-address;
        ordered-by user;
        description "DNS servers offered by the server.";
      }
      leaf domain {
        type string;
        description "DNS domain offered by the server.";
      }
      leaf server {
        type oc-inet:ipv4-address;
        description "The DHCP server that granted the lease.";
      }
      leaf lease-time {
        type uint32;
        units seconds;
        description "Lease duration granted by the server.";
      }
      leaf remaining-time {
        type uint32;
        units seconds;
        description "Time until the leased address expires.";
      }
    }
  }

  // Spanning tree. OpenConfig has identities for RSTP, MSTP and RAPID_PVST
  // only.
  identity STP {
    base oc-stp-types:STP_PROTOCOL;
    description
      "Spanning Tree Protocol, as in IEEE 802.1D-1998. Configured in
       /stp/rstp like RSTP; the bridge sends STP BPDUs only.";
    reference "IEEE 802.1D-1998 8";
  }

  // In MSTP, OpenConfig models the MSTIs (mst-id 1..4094) but not the CIST:
  // neither its bridge priority nor its port costs and priorities. These use
  // OpenConfig's own groupings.
  augment "/oc-stp:stp/oc-stp:mstp/oc-stp:config" {
    description "Bridge priority of the CIST.";
    uses oc-stp:bridge-priority-config;
  }

  augment "/oc-stp:stp/oc-stp:mstp/oc-stp:state" {
    description "Bridge priority and state of the CIST.";
    uses oc-stp:bridge-priority-config;
    uses oc-stp:stp-common-state;
  }

  augment "/oc-stp:stp/oc-stp:mstp" {
    description "Port settings and state of the CIST.";
    uses oc-stp:stp-interfaces-top;
  }

  // SNMP. snmpd needs an engine ID for USM: RFC 7407 leaves engine-id
  // optional, and USM keys are localized with the engine ID.
  augment "/snmp:snmp/snmp:engine" {
    description "State of the SNMP engine.";
    leaf engine-id-in-use {
      config false;
      type snmp:engine-id;
      description
        "The engine ID snmpd runs with: engine-id, or else one derived from
         the bridge's MAC address (RFC 3411 format 3 with Net-SNMP's
         enterprise number 8072). The USM keys of the users have to be
         localized with it.";
    }
  }
}
