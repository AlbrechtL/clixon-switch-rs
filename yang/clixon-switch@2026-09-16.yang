module clixon-switch {
  yang-version 1.1;
  namespace "urn:github:albrechtl:clixon-switch";
  prefix sw;

  // The modules imported here make up the switch's data model.
  // scripts/vendor-yang.sh copies their import closure from openconfig/public.
  import openconfig-interfaces { prefix oc-if; }
  import openconfig-if-ethernet { prefix oc-eth; }
  import openconfig-vlan { prefix oc-vlan; }
  import openconfig-vlan-types { prefix oc-vlan-types; }
  import openconfig-if-ip { prefix oc-ip; }
  import openconfig-inet-types { prefix oc-inet; }
  import openconfig-yang-types { prefix oc-yang; }
  import openconfig-spanning-tree { prefix oc-stp; }
  import openconfig-spanning-tree-types { prefix oc-stp-types; }

  organization "clixon-switch-rs";
  contact "https://github.com/AlbrechtL/clixon-switch-rs";
  description
    "Top-level module of the clixon-switch backend: switch ports in one
     VLAN-aware bridge, and routed VLAN interfaces with static IPv4
     addresses or a DHCP client, and spanning tree (STP, RSTP, MSTP), as
     modelled by OpenConfig.

     The switch runs in one of two VLAN modes (switch/config/vlan-mode):
     DOT1Q, with the VLANs declared in vlans and access or trunk ports; or
     PORT_BASED, with ports in disjoint port-based-vlans groups and no tags.

     The backend implements only part of these modules. It rejects any other
     configuration when validating a commit (see switch-model's supported.rs).
     There are no deviation statements: clixon 7.8 does not reject data for
     nodes marked 'deviate not-supported', it only skips their must
     checks.";

  revision 2026-09-16 {
    description
      "VLAN database, trunk ports, VLAN mode and port-based VLAN groups.
       State of the DHCP client's lease.
       Spanning tree: identity STP, and the CIST's bridge priority and
       ports in MSTP.
       System state: host name, OS release, uptime, load and memory.";
  }
  revision 2026-09-15 {
    description "Initial revision.";
  }

  // The VLAN database. openconfig-vlan only defines the grouping; its user,
  // openconfig-network-instance, is too big for the switch.
  uses oc-vlan:vlan-top;

  grouping switch-config {
    leaf vlan-mode {
      type enumeration {
        enum DOT1Q {
          description
            "IEEE 802.1Q: VLANs declared in /vlans, ports in access or
             trunk mode.";
        }
        enum PORT_BASED {
          description
            "Ports in disjoint groups (/port-based-vlans), untagged. Ports
             forward only to ports of their own group.";
        }
      }
      default DOT1Q;
      description "How ports are assigned to VLANs.";
    }
  }

  container switch {
    description "Switch-wide settings.";
    container config {
      uses switch-config;
    }
    container state {
      config false;
      uses switch-config;
    }
  }

  // ietf-system and openconfig-system are too big for what the switch
  // reports, and mostly configuration it does not implement.
  container system {
    description "The switch as a whole.";
    container state {
      config false;
      description "Read from /proc and os-release on every request.";
      leaf hostname {
        type string;
        description "Kernel host name.";
      }
      leaf os-name {
        type string;
        description "NAME of os-release.";
      }
      leaf os-version {
        type string;
        description "VERSION of os-release: the firmware version.";
      }
      leaf kernel-release {
        type string;
        description "Linux kernel release.";
      }
      leaf current-datetime {
        type oc-yang:date-and-time;
        description
          "System clock, in UTC. The switch has no real-time clock: it
           starts at the Unix epoch on every boot.";
      }
      leaf uptime {
        type uint64;
        units seconds;
        description "Time since boot.";
      }
      leaf load-average-1 {
        type decimal64 {
          fraction-digits 2;
        }
        description "Load average over 1 minute.";
      }
      leaf load-average-5 {
        type decimal64 {
          fraction-digits 2;
        }
        description "Load average over 5 minutes.";
      }
      leaf load-average-15 {
        type decimal64 {
          fraction-digits 2;
        }
        description "Load average over 15 minutes.";
      }
      leaf memory-total {
        type uint64;
        units kilobytes;
        description "Usable RAM (MemTotal).";
      }
      leaf memory-available {
        type uint64;
        units kilobytes;
        description
          "RAM available to new processes without swapping
           (MemAvailable).";
      }
    }
  }

  grouping port-based-vlan-group-config {
    leaf id {
      type oc-vlan-types:vlan-id;
      description
        "Group id. Also the VLAN id the group uses inside the switch, so a
         routed-vlan interface refers to the group by it.";
    }
    leaf name {
      type string;
      description "Group name; routed-vlan interfaces may refer to it.";
    }
    leaf-list port {
      type leafref {
        path "/oc-if:interfaces/oc-if:interface/oc-if:name";
      }
      description
        "Member ports. A port is a member of at most one group.";
    }
  }

  container port-based-vlans {
    description
      "Port-based VLAN groups, used in vlan-mode PORT_BASED only.";
    list group {
      key "id";
      leaf id {
        type leafref {
          path "../config/id";
        }
      }
      container config {
        uses port-based-vlan-group-config;
      }
      container state {
        config false;
        uses port-based-vlan-group-config;
      }
    }
  }

  // OpenConfig models only whether a DHCP client runs
  // (ipv4/config/dhcp-client) and the origin of an address, not the lease.
  augment "/oc-if:interfaces/oc-if:interface/oc-vlan:routed-vlan/"
        + "oc-ip:ipv4/oc-ip:state" {
    description
      "DHCP client lease of a routed VLAN interface.";
    container dhcp-lease {
      description
        "The lease the DHCP client currently holds. Absent while
         ipv4/config/dhcp-client is false or no lease is bound.";
      leaf address {
        type oc-inet:ipv4-address;
        description "Leased address.";
      }
      leaf prefix-length {
        type uint8 {
          range "0..32";
        }
        description "Prefix length of the leased address.";
      }
      leaf-list router {
        type oc-inet:ipv4-address;
        ordered-by user;
        description
          "Routers offered by the server. The first one is the default
           gateway.";
      }
      leaf-list dns-server {
        type oc-inet:ipv4-address;
        ordered-by user;
        description "DNS servers offered by the server.";
      }
      leaf domain {
        type string;
        description "DNS domain offered by the server.";
      }
      leaf server {
        type oc-inet:ipv4-address;
        description "The DHCP server that granted the lease.";
      }
      leaf lease-time {
        type uint32;
        units seconds;
        description "Lease duration granted by the server.";
      }
      leaf remaining-time {
        type uint32;
        units seconds;
        description "Time until the leased address expires.";
      }
    }
  }

  // Spanning tree. OpenConfig has identities for RSTP, MSTP and RAPID_PVST
  // only.
  identity STP {
    base oc-stp-types:STP_PROTOCOL;
    description
      "Spanning Tree Protocol, as in IEEE 802.1D-1998. Configured in
       /stp/rstp like RSTP; the bridge sends STP BPDUs only.";
    reference "IEEE 802.1D-1998 8";
  }

  // In MSTP, OpenConfig models the MSTIs (mst-id 1..4094) but not the CIST:
  // neither its bridge priority nor its port costs and priorities. These use
  // OpenConfig's own groupings.
  augment "/oc-stp:stp/oc-stp:mstp/oc-stp:config" {
    description "Bridge priority of the CIST.";
    uses oc-stp:bridge-priority-config;
  }

  augment "/oc-stp:stp/oc-stp:mstp/oc-stp:state" {
    description "Bridge priority and state of the CIST.";
    uses oc-stp:bridge-priority-config;
    uses oc-stp:stp-common-state;
  }

  augment "/oc-stp:stp/oc-stp:mstp" {
    description "Port settings and state of the CIST.";
    uses oc-stp:stp-interfaces-top;
  }
}
